import FreeCAD

# Get the active document
doc = FreeCAD.ActiveDocument

availableSheets = doc.findObjects("Spreadsheet::Sheet")
dimensionSheet = availableSheets[0]

# Check if the document is not empty
if doc is not None:
    # Remplace each drawing template with own template
    templates = doc.findObjects("TechDraw::DrawSVGTemplate")
    for template in templates:
        template.Template = "../templates/A4_LandscapeTD.svg"
    # Iterate through all pages in the TechDraw Workbench
    # pages = doc.findObjects("TechDraw::DrawPage")
    pages = doc.getObjectsByLabel("drawings")[0].Group
    pageNumber = 1
    for page in pages:
        templateTexts = page.Template.EditableTexts
        # Change the title of each page
        templateTexts["FC-Title"] = dimensionSheet.project_title
        templateTexts["Designed_by_Name"] = dimensionSheet.project_author
        templateTexts["Subtitle"] = page.Label
        templateTexts["FC-Date"] = dimensionSheet.project_date
        templateTexts["FC-SH"] = str(pageNumber)
        templateTexts["FC-SC"] = str(page.Scale)
        # templateTexts["Quantity"] = "1"
        templateTexts["Drawing_number"] = dimensionSheet.project_code
        pageNumber = pageNumber + 1
        page.Template.EditableTexts = templateTexts
    # Add ArcCenterMarks to each object
    views = doc.findObjects("TechDraw::DrawViewPart")
    for view in views:
       view.ViewObject.ArcCenterMarks = True
       view.CoarseView = False

    # Save the document
    doc.recompute()
    doc.save()

else:
    print("No active document.")
